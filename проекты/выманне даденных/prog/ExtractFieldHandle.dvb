Attribute VB_Name = "Module1"
Public Sub ExtractFieldHandle()
    On Error Resume Next
    Dim hTbl As String: hTbl = ThisDrawing.GetVariable("USERS1")
    Dim r As Integer: r = ThisDrawing.GetVariable("USERI1")
    Dim c As Integer: c = ThisDrawing.GetVariable("USERI2")
    
    Dim tbl As AcadTable
    Set tbl = ThisDrawing.HandleToObject(hTbl)
    
    If Not tbl Is Nothing Then
        Dim fId As LongPtr
        fId = tbl.GetFieldId2(r, c, 0)
        
        If fId <> 0 And fId <> 43 Then
            Dim fObj As AcadObject
            Set fObj = ThisDrawing.ObjectIdToObject(fId)
            If Not fObj Is Nothing Then
                ' ПРИНУДИТЕЛЬНО ВЫЧИСЛЯЕМ (убирает решетки ####)
                fObj.Evaluate
                ' Возвращаем хэндл в Лисп
                ThisDrawing.SetVariable "USERS1", fObj.Handle
                Exit Sub
            End If
        End If
    End If
    ThisDrawing.SetVariable "USERS1", ""
End Sub

Attribute VB_Name = "Module2"
Public Sub VbaWriteField()
    On Error Resume Next
    Dim hTbl As String: hTbl = ThisDrawing.GetVariable("USERS1")
    Dim r As Integer: r = ThisDrawing.GetVariable("USERI1")
    Dim c As Integer: c = ThisDrawing.GetVariable("USERI2")
    Dim fldText As String: fldText = ThisDrawing.GetVariable("USERS2")
    
    Dim tbl As AcadTable
    Set tbl = ThisDrawing.HandleToObject(hTbl)
    
    If Not tbl Is Nothing Then
        ' 1. Записываем строку (Именно SetTextString создает настоящие поля!)
        tbl.SetTextString r, c, 0, fldText
        
        ' 2. Находим созданное поле и вычисляем его в памяти
        Dim fId As LongPtr
        fId = tbl.GetFieldId2(r, c, 0)
        
        If fId <> 0 And fId <> 43 Then
            Dim fObj As AcadObject
            Set fObj = ThisDrawing.ObjectIdToObject(fId)
            If Not fObj Is Nothing Then
                fObj.Evaluate ' Вычисляем скрытую формулу
            End If
        End If
        
        ' 3. Заставляем таблицу перерисовать графику ячеек
        tbl.RecomputeTableBlock True
    End If
End Sub
